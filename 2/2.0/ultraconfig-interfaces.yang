module ultraconfig-interfaces {

yang-version 1.1;

namespace
        "http://ultraconfig.com.au/ns/yang/ultraconfig-interfaces";

prefix if;

organization
        "Ultra Config Pty Ltd";

contact
        "Support: <https://ultraconfig.com.au/contact/>";

description
        "This YANG module has been created for the purpose of a tutorial.
        It defines the model for a basic ethernet interface";

revision "2020-01-03" {
        description
                "Initial Revision";
        reference
                "Learn YANG - Full Tutorial for Beginners";

}

typedef dotted-quad {
  type string {
    pattern
      '(([0-9]|[1-9][0-9]|1[0-9][0-9]|2[0-4][0-9]|25[0-5])\.){3}'
        + '([0-9]|[1-9][0-9]|1[0-9][0-9]|2[0-4][0-9]|25[0-5])';
  }
  description
    "Four octets written as decimal numbers and
     separated with the '.' (full stop) character.";
}
}
